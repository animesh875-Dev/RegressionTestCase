# IBM Engineering Requirements Fri Dec 09 08:47:12 CET 2022

# Specification: CAT reqif M
- Artifact Format: Module
- ReqIF.Name: CAT reqif M

## 318238: Cat reqif A1
- Artifact Format: Text
- AAAA1: false
- Status: Draft

## 318239: download1.jpg
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- AAAA1: false
- Artifact Format: File
- Status: Draft
