# IBM Engineering Requirements Mon Jun 24 18:41:53 CEST 2024

# Specification: testcase_module
- ReqIF.Name: testcase_module
- Artifact Format: Module

## 2273022: testcase_artifact
- Artifact Format: Text
