# IBM Rational Requirements Thu May 27 11:01:06 CEST 2021

# Specification: Import ReqIF
- ReqIF.Name: Import ReqIF
- Artifact Format: Module

## 2002294: Artifact 1 - Information (Information [DNG-Renamed-2])
- Status [DNG-Renamed-2]: NEW/CHANGED
- Artifact Format: Text

## 2002295: Artifact 2 - Information (Information [DNG-Renamed-2])
- Status [DNG-Renamed-2]: NEW/CHANGED
- Artifact Format: Text

## 2002296: Artifact 3 - Heading (Heading [DNG-Renamed-2])
- Artifact Format: Text
- Status [DNG-Renamed-2]: NEW/CHANGED

## 2002297: Artifact 4 - Heading (Heading [DNG-Renamed-2])
- Artifact Format: Text
- Status [DNG-Renamed-2]: NEW/CHANGED

## 2002298: Artifact 5 - Term action (Term-Action)
- Artifact Format: Text

## 2002299: Artifact 6 - Term action (Term-Action)
- Artifact Format: Text
