# IBM Engineering Requirements Fri Jan 13 11:44:41 CET 2023

# Specification: TestNewArtifact_EditName_AfterBaseline
- Artifact Format: Module
- ReqIF.Name: TestNewArtifact_EditName_AfterBaseline

## 2454083: qwe11111111 (Heading)
- Deviation Exist: No
- Heading: 10
- Artifact Format: Text
- Name: qwe
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
## 2454085: 10 (Heading)
- Deviation Exist: No
- ChapterName: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
- Artifact Format: Text

## 2454086: Cat reqif A3 (Heading)
- Deviation Exist: No
- Artifact Format: Text
- ChapterName: Cat reqif A3
  | Header | Value |
  | --- | --- |
- Heading: 10

## 2454087: Cat reqif A4 Symbols (Heading)
- Artifact Format: Text
- Deviation Exist: No
- Heading: 10
- ChapterName: Cat reqif A4 Symbols
  ✓ψ≅→™∝∑®

## 2454093: Cat reqif A5 Artifact (Information)
- Platform Category: Core
- Artifact Format: Text
- Heading: 10
- Deviation Exist: No

## 2454084: 10 (Heading)
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- Artifact Format: File
- Deviation Exist: No
- Name: img-01111616.png
