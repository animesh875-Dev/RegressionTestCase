# IBM Engineering Requirements Sun Dec 25 11:41:11 CET 2022

# Specification: CAT reqif M
- ReqIF.Name: CAT reqif M
- Artifact Format: Module

## 3329166: Cat reqif A1 (Heading)
- Artifact Format: Text
- ED_rv_subsys_type: Hydraulic unit, Actuator
- ED_Valve_variant: 3-port bypass valve, 3-port dual expansion valve, 3-port switch over valve, 2-port expansion valve

## 3329167 (Feature)
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- Artifact Format: Text

## 3329169: Cat reqif A3 | Header | Value | | --- | --- | (Heading)
- ED_Valve_variant: 2-port expansion valve, 3-port bypass valve, 3-port dual expansion valve, 3-port switch over valve
- ED_rv_subsys_type: Actuator, Hydraulic unit
- Name: Cat reqif A3
- Artifact Format: Text

## 3329170: Cat reqif A4 Symbols (Information)
Cat reqif A4 Symbols
✓ψ≅→™∝∑®
- ED_Valve_variant: 3-port bypass valve, 3-port switch over valve, 3-port dual expansion valve, 2-port expansion valve
- ED_rv_subsys_type: Hydraulic unit, Actuator
- Artifact Format: Text
- Status_Stakeholder: new/changed

## 3329171: Cat reqif A5 Artifact (Information)
Cat reqif A5 Artifact
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- ED_Valve_variant: 2-port expansion valve, 3-port dual expansion valve, 3-port switch over valve, 3-port bypass valve
- ED_rv_subsys_type: Hydraulic unit, Actuator
- Artifact Format: Text
- Status_Stakeholder: new/changed

# Specification: CAT reqif M2
- ReqIF.Name: CAT reqif M2
- Artifact Format: Module

## 3329163: CAT reqif M2 (Design Requirement)
CAT reqif M2
| Header | Value |
| --- | --- |
- Artifact Format: Text

## 3329164: cat r2 reqif2 (Information)
- ED_Valve_variant: 3-port dual expansion valve, 3-port switch over valve, 3-port bypass valve, 2-port expansion valve
- Status_Stakeholder: new/changed
- Artifact Format: Text
- ED_rv_subsys_type: Hydraulic unit, Actuator

## 3329168: img-12251548.png (Feature)
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- Artifact Format: File

## 3329164: cat r2 reqif2 (Information)
- ED_Valve_variant: 3-port bypass valve, 3-port dual expansion valve, 2-port expansion valve, 3-port switch over valve
- ED_rv_subsys_type: Hydraulic unit, Actuator
- Status_Stakeholder: new/changed
- Artifact Format: Text
