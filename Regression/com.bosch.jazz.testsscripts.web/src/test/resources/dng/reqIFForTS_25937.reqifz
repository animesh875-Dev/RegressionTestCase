# Specification V1.pdf_v1

# Specification: Specification V1.pdf

## R1
Die Farbe des Grundkörpers soll
grün sein.
The colour of the Body should be green.
- CustomerPrefix: ID-1
- Type.Name: Requirement

## R2
Das Material darf nicht entflammbar
sein.
Material must not be flammable.
- CustomerPrefix: ID-10
- Type.Name: Requirement

## R3
Das Gewicht soll zwischen 17 und
19.5 kg liegen.
Weight has to be between 17 and 18.5
kg.
- CustomerPrefix: ID-100
- Type.Name: Requirement

## R4
Die Dichte des Basismaterials soll
größer sein als die des
Deckmaterials.
Density of the base material has to be
higher
than the material used as cover.
- CustomerPrefix: ID-1000
- Type.Name: Requirement

## R5
Das Objekt soll wasserresistent sein.
Object has to be water resistant.
- CustomerPrefix: ID-1001
- Type.Name: Requirement

## R6
Die Objektausprägung soll gemäß
der nachstehenden Tabelle
erfolgen:
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The object should be in alignment with
the following table:
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- CustomerPrefix: ID-0815
- Type.Name: Requirement

## R7
Das Objekt soll resistent gegen
Säuren sein.
Object has to be acid resistant.
- CustomerPrefix: ID-12345
- Type.Name: Requirement

## R8
Der Lieferzeitraum soll weniger als 3
Wochen betragen.
Delivery time has to be less than 4
weeks.
- CustomerPrefix: ID-12345
- Type.Name: Requirement

## R9
Die Produktion soll unter
Berücksichtigung der DIN 4711
stattfinden.
Production processes have to take DIN
4711 into
account.
- CustomerPrefix: ID-891011
- Type.Name: Requirement

## R10
Sammlung Sonderzeichen:
∆∏∑©¶ŊɸΦαβγδεμπ①②⓫⓬
→←-¼-a²-½-b³-¾
List of Symbols:
∆∏∑©¶ŊɸΦαβγδεμπ①②⓫⓬→←-
¼-a²-½-b³-¾
- CustomerPrefix: ID-484951
- Type.Name: Requirement

## R11
Chinesische und japanische Zeichen
„ein Tag voller Freude“:
艾因标签沃勒尔依此解释アインタグ
フェラーフロイデ
Chinese and japanese signs „a day full of
happyness“:
艾因标签沃勒尔依此解释アインタグフ
ェラーフロイデ
- CustomerPrefix: ID-484951
- Type.Name: Requirement

## R12
Die Transportzeit soll nicht höher als
4 Stunden betragen.
Transport time has to be less than 4
hours.
- CustomerPrefix: ID-131415
- Type.Name: Requirement

## R13
Die Höhe des Objektes darf 2.5
Meter nicht überschreiten.
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Height <= 2.5 m.
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- CustomerPrefix: ID-171819
- Type.Name: Requirement

## R14
Die Breite des Objektes soll kleiner
als 2.2 Meter sein.
Wide <= 1.2 m.
- CustomerPrefix: ID-212223
- Type.Name: Requirement

## R15
Die Tiefe des Objektes darf maximal
1.6 Meter betragen.
Depth <= 1.6 m.
- CustomerPrefix: ID-252627
- Type.Name: Requirement

## R16
Reaktion des Systems gemäß Formel
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System should react on the basis of
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- CustomerPrefix: ID-252628
- Type.Name: Requirement

## R17
Sollte ein Fehlverhalten auftreten,
soll das Objekt den Endnutzer
darüber automatisch informieren.
Dabei soll der Weg der Information
abhängig von den
Außenparametern in Echtzeit
automatisiert festgelegt werden.
In case of a failure, object should inform
the end
user automatically. Way of information
has to be
detected in real time by the object.
- CustomerPrefix: ID-293031
- Type.Name: Requirement

## R18
Sollten Beschädigungen der
Außenhülle auftreten, soll die innere
Schalteinheit automatisch
herunterfahren.
In case of damages of outer casing, inner
circuits
have to shut down automatically.
- CustomerPrefix: ID-333435
- Type.Name: Requirement

## R19
Fallversuche aus 3 Metern Höhe
sollen vom Objekt in der Form
überstanden werden, dass ein
Funktionieren unter allen
Umständen gewährleistet ist.
Dropping from 3 meter height should
not have
influences to functionality.
- CustomerPrefix: ID-373839
- Type.Name: Requirement

## R20: 2
Object Requirements
- ChapterName: Objektanforderungen
- Type.Name: Heading

### R21
Das Objekt soll zu Transportzwecken
in drei ähnlich große Teile zerlegt
werden können.
Object should be de-assembled to 3
parts with
similar dimensions.
- CustomerPrefix: ID-444546
- Type.Name: Requirement

### R22
Ein Zusammenbau in falscher
Reihenfolge soll durch mechanische
Maßnahmen verhindert werden.
Diese Maßnahmen dürfen in Summe
nicht mehr als 2% der Herstellkosten
betragen.
Correct re-assembling should be
supported by
mechanical supports.
- CustomerPrefix: ID-484950
- Type.Name: Requirement

## R23: 3
Flow Volume
- ChapterName: Durchflußvolumen
- Type.Name: Heading

### R24
Das Durchflußvolumen soll in
niedrigster Betriebsstufe 3 m³ nicht
unterschreiten.
Flow volume should be higher than 3
m³ with
usage level 1.
- CustomerPrefix: ID-525354
- Type.Name: Requirement

### R25
Das Durchflußvolumen soll in
höchster Betriebsstufe 24 m³ nicht
unterschreiten.
Flow volume should be higher than 25
m³ with
highest usage level.
- CustomerPrefix: ID-565758
- Type.Name: Requirement

### R26
Das Durchflußvolumen darf durch
Temperatureinflüsse nicht variieren.
Volume flow should be independent
from
temperature.
- CustomerPrefix: ID-606162
- Type.Name: Requirement

## R27: 4
Handling
- ChapterName: Bedienung
- Type.Name: Heading

### R28
Eine Bedieneinheit soll das
gefahrlose Ein- und Ausschalten
gewährleisten.
English - This is an English text, used to
represent
requirements in a foreign language
and not too
short for test purposes - 23
- CustomerPrefix: ID-646566
- Type.Name: Requirement

### R29
DIN 4712 ist bei der Auslegung der
Schalterpositionen zu beachten.
English - This is an English text, used to
represent
requirements in a foreign language
and not too
short for test purposes - 24
- CustomerPrefix: ID-686970
- Type.Name: Requirement

### R30
Im Falle einer Verwendung eines
Zwischengetriebes ist die
Betriebsdauer des Gesamtsystems
auf die des Zwischengetriebes
abzustellen.
English - This is an English text, used to
represent
requirements in a foreign language
and not too
short for test purposes - 25
- CustomerPrefix: ID-727374
- Type.Name: Requirement

### R31
Die Wartungsintervalle sollen größer
14 Monate liegen.
English - This is an English text, used to
represent
requirements in a foreign language
and not too
short for test purposes - 26
- CustomerPrefix: ID-767778
- Type.Name: Requirement

### R32
Eine Betriebsstrecken-abhängige
Wartung ist zu vermeiden.
English - This is an English text, used to
represent
requirements in a foreign language
and not too
short for test purposes - 27
- CustomerPrefix: ID-808182
- Type.Name: Requirement

### R33
Deutsch - Dies ist ein deutscher Test-
Text mit fortlaufender Nummer zur
Abgrenzung. Die Menge der Daten
soll dadurch auf eine erwartet
durchschnittliche Größe erhöht
werden, um eine realistische Basis
für eine Performance-Abschätzung
zu erhalten und darauf basierend
Aussagen zur Leistungsfähigkeit von
ReqMan ableiten zu können - 28
English - This is an English text, used to
represent requirements in a foreign
language and not too short for test
purposes - 28
- CustomerPrefix: ID-000028
- Type.Name: Requirement

### R34
Deutsch - Dies ist ein deutscher Test-
Text mit fortlaufender Nummer zur
Abgrenzung. Die Menge der Daten
soll dadurch auf eine erwartet
durchschnittliche Größe erhöht
werden, um eine realistische Basis
für eine Performance-Abschätzung
zu erhalten und darauf basierend
Aussagen zur Leistungsfähigkeit von
ReqMan ableiten zu können - 29
English - This is an English text, used to
represent requirements in a foreign
language and not too short for test
purposes - 29
- CustomerPrefix: ID-000029
- Type.Name: Requirement
