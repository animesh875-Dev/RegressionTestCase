# IBM Engineering Requirements Tue Dec 20 11:00:00 CET 2022

# Specification: CAT reqif M
- Artifact Format: Module
- ReqIF.Name: CAT reqif M

## 318238: Cat reqif A1 (Heading)
- Artifact Format: Text
- Status: Draft
- AAAA1: false

## 318239: download1.jpg (Heading)
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- AAAA1: false
- Status: Draft
- Artifact Format: File

## 318657: Cat reqif A3 (Design Requirement)
Cat reqif A3
| Header | Value |
| --- | --- |
- Artifact Format: Text

## 318658: Cat reqif A4 Symbols ✓ψ≅→™∝∑® (Heading)
- AAAA1: false
- Artifact Format: Text
- Status: Draft
- Name: Cat reqif A4 Symbols

## 318659: Cat reqif A5 Artifact (Information)
Cat reqif A5 Artifact
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Link
318241: cat r1 reqif
- Artifact Format: Text

# Specification: CAT reqif M2
- AAAA1: false
- Status: Draft
- ApplicableFrom: any
- ReqIF.Name: CAT reqif M2
- Artifact Format: Module

## 318241: cat r1 reqif (Design Requirement)
cat r1 reqif
| head | value |
| --- | --- |
- Artifact Format: Text

## 318656: cat r2 reqif2 (Design Requirement)
- Artifact Format: Text

## 318656: cat r2 reqif2 (Design Requirement)
- Artifact Format: Text

## 318241: cat r1 reqif (Design Requirement)
cat r1 reqif
| head | value |
| --- | --- |
- Artifact Format: Text
