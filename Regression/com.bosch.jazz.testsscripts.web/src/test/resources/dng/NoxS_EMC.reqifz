# IBM Rational Requirements Tue Nov 14 14:05:30 CET 2017

# Specification: NoxS_EMC
- Artifact Format: Module
- ReqIF.Name: NoxS_EMC
- ReqIF.Description: KLH-Modul deutsch

## 876983: Elektromagnetische Verträglichkeit (EMV) (Heading Customer)
- Customer ID: STLH-3041
- Artifact Format: Text

### 876984: Ansprechpartner für EMV (Customer Requirement)
Ansprechpartner für EMV
Name, Vorname: Pohl, Christof
Abteilung: RD/EIB
E-Mail: emv-team@daimler.com
- Artifact Format: Text
- Acceptance: in evaluation
- Customer ID: STLH-1499

### 876985: Allgemeine EMV-Anforderungen (Heading Customer)
- Customer ID: STLH-3804
- Artifact Format: Text

#### 876986 (Customer Requirement)
Der Gesamtumfang der Messverfahren und Messaufbauten sowie Grenzwerte sind in [MBN 10284-1] "EMV-Anforderungen – Fahrzeugprüfung" und [MBN 10284-2] "EMV-Anforderungen – Komponentenprüfung (PKW und Transporter)" beschrieben. Die Schärfegrade und Prüfparameter sind in Abstimmung mit der Entwicklungsabteilung und der EMV-Fachabteilung des Auftraggebers festzulegen.
- Customer ID: STLH-3805
- Acceptance: in evaluation
- Artifact Format: Text

#### 876987 (Customer Requirement)
Ein Testplan ist vom Auftragnehmer zu erstellen. Der Testplan muss vor Durchführung der Komponentenprüfungen von der EMV-Fachabteilung des Auftraggebers freigegeben werden. Eine Vorlage für Testplan und Komponentenprüfbericht kann unter der E-Mail-Adresse emv-team@daimler.com angefordert werden.
- Acceptance: in evaluation
- Customer ID: STLH-3806
- Artifact Format: Text

#### 876988: Nach Durchführung der Tests ist der Komponentenprüfbericht an den verantwortlichen Entwicklungsingenieur und an die EMV-Fachabteilung des Auftraggebers zu senden. (Customer Requirement)
- Acceptance: in evaluation
- Artifact Format: Text
- Customer ID: STLH-3808

#### 876989: Abgabetermin für den abgestimmten Testplan: »spätestens 5 Monate nach Vergabe« (Customer Requirement)
- Artifact Format: Text
- Customer ID: STLH-3807
- Acceptance: in evaluation

#### 876990: Abgabetermin für den Komponentenprüfbericht: »mindestens 2 Wochen vor der Fahrzeugprüfung, spätestens jedoch zum C-Muster« (Customer Requirement)
- Artifact Format: Text
- Customer ID: STLH-3809
- Acceptance: in evaluation

#### 876991: Testplan und Komponentenprüfbericht sind an folgende E-Mail-Adresse zu senden: emv-team@daimler.com (Customer Requirement)
- Customer ID: STLH-3810
- Artifact Format: Text
- Acceptance: in evaluation

#### 876992: Die finale Freigabe der Komponente erfolgt anhand der Messergebnisse im Fahrzeug. (Customer Requirement)
- Artifact Format: Text
- Customer ID: STLH-4697
- Acceptance: in evaluation

#### 876993: Für weitere Fragen wenden Sie sich bitte an die EMV-Fachabteilung des Auftraggebers. (Information)
- Artifact Format: Text
- Customer ID: STLH-4022

### 876994: Komponenten mit Bussystemen (CAN, LIN, FlexRay, Ethernet ...) (Heading Customer)
- Artifact Format: Text
- Customer ID: STLH-3812

#### 876995: Um die Einsatzfähigkeit der Bussysteme zu gewährleisten, dürfen die Bussysteme bei allen Störfestigkeitsanforderungen keinesfalls beeinträchtigt oder gar blockiert werden. (Customer Requirement)
- Customer ID: STLH-3813
- Acceptance: in evaluation
- Artifact Format: Text

### 876996: ESD-Anforderungen (Heading Customer)
- Customer ID: STLH-3814
- Artifact Format: Text

#### 876997: Allgemeines (Heading Customer)
- Customer ID: STLH-3815
- Artifact Format: Text

##### 876998: Für die ESD-gerechte Fertigung/Montage von ESD-sensitiven Komponenten ist ein Nachweis in Form eines ESD-Audits vorzulegen (verankert in der [MBN 10447] "Qualitätsmanagement-Norm Elektrik/Elektronik für Mercedes-Benz Cars"). (Customer Requirement)
- Artifact Format: Text
- Customer ID: STLH-3816
- Acceptance: in evaluation

##### 876999: ESD-sensitive Komponenten (siehe Einstufung unter Kapitel "Einstufung bzgl. Elektrostatischer Sensitivität" unter der Anforderungs-ID STLH-3820) sind ESD-gerecht zu handhaben und zu verpacken. (Customer Requirement)
- Customer ID: STLH-3818
- Artifact Format: Text
- Acceptance: in evaluation

##### 877000: ESD-Anforderungen an die Verpackung für Serien- und Ersatzteile sind in STLH-1191 Kapitel "Lagerfähigkeit, Verpackung und Transport" beschrieben. (Customer Requirement)
- Customer ID: STLH-3819
- Artifact Format: Text
- Acceptance: in evaluation

#### 877001: Einstufung bzgl. elektrostatischer Sensitivität (Heading Customer)
- Customer ID: STLH-3820
- Artifact Format: Text

##### 877002 (Customer Requirement)
Die Komponente ist elektrostatisch sensitiv
ja
- Artifact Format: Text
- Customer ID: STLH-3821
- Acceptance: in evaluation

### 877003: Testbedingungen (Heading Customer)
- Customer ID: STLH-3822
- Artifact Format: Text

#### 877004: Betriebszustände (Heading Customer)
- Customer ID: STLH-3823
- Artifact Format: Text

##### 877005: Die Komponente muss in den folgenden Betriebszuständen geprüft werden: (Customer Requirement)
- Customer ID: STLH-3824
- Artifact Format: Text
- Acceptance: in evaluation

##### 877006: Name des Betriebszustands »...« (Customer Requirement)
Name des Betriebszustands »...«
Beschreibung des Betriebszustands »...«
- Acceptance: in evaluation
- Customer ID: STLH-3825
- Artifact Format: Text

##### 877007: Anmerkung: Die detaillierten Beschreibungen der Betriebszustände können im Testplan angepasst werden. Änderungen und Ergänzungen sind mit dem Auftraggeber abzustimmen. (Customer Requirement)
- Acceptance: in evaluation
- Customer ID: STLH-6238
- Artifact Format: Text

#### 877008: Prüfkriterien (Heading Customer)
- Customer ID: STLH-3826
- Artifact Format: Text

##### 877009: Der Auftraggeber stuft die möglichen Effekte oder Funktionsabweichungen während des Tests in drei unterschiedliche Kategorien (1, 2 oder 3) ein, basierend auf ihren Auswirkungen auf Kunden. (Customer Requirement)
- Acceptance: in evaluation
- Customer ID: STLH-3827
- Artifact Format: Text

##### 877010: Alle nicht spezifizierten Effekte oder Funktionsabweichungen fallen automatisch in die Kategorie 3. (Customer Requirement)
- Acceptance: in evaluation
- Customer ID: STLH-4203
- Artifact Format: Text

##### 877011: Möglicher Effekt: »...« (Customer Requirement)
Möglicher Effekt: »...«
Kategorie: »...« "1/2/3"
Zu überwachende Funktion: »...«
- Customer ID: STLH-3829
- Acceptance: in evaluation
- Artifact Format: Text

##### 877012: Anmerkung: Weitere mögliche Effekte und die dazugehörigen Kategorien können im Testplan ergänzt werden. Änderungen und Ergänzungen sind mit dem Auftraggeber abzustimmen. (Customer Requirement)
- Artifact Format: Text
- Acceptance: in evaluation
- Customer ID: STLH-6239

### 877013: EMV-Anforderungen – Komponentenprüfungen (Heading Customer)
- Customer ID: STLH-3830
- Artifact Format: Text

#### 877014: HF-Emissionen – Messungen an der Netznachbildung (AN-Test) (Heading Customer)
- Artifact Format: Text
- Customer ID: STLH-3831

##### 877015: Betriebszustände des Prüflings während des Tests (definiert in Kapitel Betriebszustände): »...« (Customer Requirement)
- Customer ID: STLH-3832
- Acceptance: in evaluation
- Artifact Format: Text

##### 877016: Weitere Details sind in [MBN 10284-2] im Kapitel 6 zu finden. (Customer Requirement)
- Customer ID: STLH-3834
- Acceptance: in evaluation
- Artifact Format: Text

#### 877017: HF-Emissionen – Messung mit Antennen (RE-Test) (Heading Customer)
- Customer ID: STLH-3843
- Artifact Format: Text

##### 877018: Betriebszustände des Prüflings während des Tests (definiert in Kapitel Betriebszustände): »...« (Customer Requirement)
- Customer ID: STLH-3844
- Artifact Format: Text
- Acceptance: in evaluation

##### 877019: Weitere Details sind in [MBN 10284-2] im Kapitel 7 zu finden. (Customer Requirement)
- Customer ID: STLH-3846
- Artifact Format: Text
- Acceptance: in evaluation

#### 877020: HF-Emissionen – Antennennahfeld (NFA-Test) (Heading Customer)
- Customer ID: STLH-3835
- Artifact Format: Text

##### 877021: Betriebszustände des Prüflings während des Tests (definiert in Kapitel Betriebszustände): »...« (Customer Requirement)
- Customer ID: STLH-3836
- Acceptance: in evaluation
- Artifact Format: Text

##### 877022: Weitere Details sind in [MBN 10284-2] im Kapitel 8 zu finden. (Customer Requirement)
- Artifact Format: Text
- Acceptance: in evaluation
- Customer ID: STLH-3838

#### 877023: Emissionen – Messung Magnetfeld mit isotroper Prüfsonde (ICNIRP-Test) (Heading Customer)
- Artifact Format: Text
- Customer ID: STLH-6240

##### 877024: Betriebszustände des Prüflings während des Tests (definiert in Kapitel Betriebszustände): »...« (Customer Requirement)
- Artifact Format: Text
- Customer ID: STLH-6241
- Acceptance: in evaluation

##### 877025: Weitere Details sind in [MBN 10284-2] im Kapitel 9 zu finden. (Customer Requirement)
- Customer ID: STLH-6242
- Artifact Format: Text
- Acceptance: in evaluation

#### 877026: Transiente Emissionen auf Versorgungsleitungen (CTE-Test) (Heading Customer)
- Customer ID: STLH-3847
- Artifact Format: Text

##### 877027: Zu messen sind die transienten Emissionen bei folgenden Schaltereignissen des Prüflings: Einschalten, Ausschalten, Schalten von angeschlossenen Aktoren. (Customer Requirement)
- Artifact Format: Text
- Acceptance: in evaluation
- Customer ID: STLH-3848

##### 877028: Weitere Details sind in [MBN 10284-2] im Kapitel 10 zu finden. (Customer Requirement)
- Customer ID: STLH-3850
- Artifact Format: Text
- Acceptance: in evaluation

#### 877029: HF-Störfestigkeit – Antenneneinstrahlung (BCI-Test) (Heading Customer)
- Customer ID: STLH-3851
- Artifact Format: Text

##### 877030: Betriebszustände des Prüflings während des Tests (definiert in Kapitel Betriebszustände): »...« (Customer Requirement)
- Customer ID: STLH-3852
- Artifact Format: Text
- Acceptance: in evaluation

##### 877031: Weitere Details sind in [MBN 10284-2] im Kapitel 12 zu finden. (Customer Requirement)
- Acceptance: in evaluation
- Artifact Format: Text
- Customer ID: STLH-3854

#### 877032: HF-Störfestigkeit; OPTION 1 – Antenneneinstrahlung (ALSE-Test); OPTION 2 – Modenverwirbelungskammer (CRC-Test) (Heading Customer)
- Customer ID: STLH-3855
- Artifact Format: Text

##### 877033: Betriebszustände des Prüflings während des Tests (definiert in Kapitel Betriebszustände): »...« (Customer Requirement)
- Artifact Format: Text
- Customer ID: STLH-3856
- Acceptance: in evaluation

##### 877034: Weitere Details sind in [MBN 10284-2] im Kapitel 13 (ALSE-Test) bzw. Kapitel 14 (CRC-Test) zu finden. (Customer Requirement)
- Artifact Format: Text
- Customer ID: STLH-3858
- Acceptance: in evaluation

#### 877035: Störfestigkeit der Magnetfelder (LFM-Test) (Heading Customer)
- Artifact Format: Text
- Customer ID: STLH-3863

##### 877036: Betriebszustände des Prüflings während des Tests (definiert in Kapitel Betriebszustände): »...« (Customer Requirement)
- Acceptance: in evaluation
- Artifact Format: Text
- Customer ID: STLH-3864

##### 877037: Weitere Details sind in [MBN 10284-2] im Kapitel 15 zu finden. (Customer Requirement)
- Artifact Format: Text
- Customer ID: STLH-3866
- Acceptance: in evaluation

#### 877038: Transienten auf Versorgungsleitungen (TSUP-Test) (Heading Customer)
- Artifact Format: Text
- Customer ID: STLH-3867

##### 877039: Betriebszustände des Prüflings während des Tests (definiert in Kapitel Betriebszustände): »...« (Customer Requirement)
- Customer ID: STLH-3868
- Acceptance: in evaluation
- Artifact Format: Text

##### 877040: Weitere Details sind in [MBN 10284-2] im Kapitel 16 zu finden. (Customer Requirement)
- Customer ID: STLH-3870
- Acceptance: in evaluation
- Artifact Format: Text

#### 877041: Transienten auf Leitungen außer Versorgungsleitungen (TOL-Test) (Heading Customer)
- Artifact Format: Text
- Customer ID: STLH-3871

##### 877042: Betriebszustände des Prüflings während des Tests (definiert in Kapitel Betriebszustände): »...« (Customer Requirement)
- Customer ID: STLH-3872
- Acceptance: in evaluation
- Artifact Format: Text

##### 877043: Weitere Details sind in [MBN 10284-2] im Kapitel 17 zu finden. (Customer Requirement)
- Acceptance: in evaluation
- Artifact Format: Text
- Customer ID: STLH-3874

#### 877044: Elektrostatische Entladung – Handling Test (ESDH-Test) (Heading Customer)
- Customer ID: STLH-3875
- Artifact Format: Text

##### 877045: Betriebszustand der Komponente während des Tests: stromlos, Komponente nicht angeschlossen (Customer Requirement)
- Artifact Format: Text
- Acceptance: in evaluation
- Customer ID: STLH-3876

##### 877046: Entladenetzwerk (ESDH-Test): 150 pF / 330 Ω (Customer Requirement)
- Acceptance: in evaluation
- Artifact Format: Text
- Customer ID: STLH-3879

##### 877047: Weitere Details sind in [MBN 10284-2] im Kapitel 18 zu finden. (Customer Requirement)
- Customer ID: STLH-3880
- Acceptance: in evaluation
- Artifact Format: Text

#### 877048: Elektrostatische Entladung (Powered Up) – Direkte Entladung (ESDD-Test) (Heading Customer)
- Artifact Format: Text
- Customer ID: STLH-3881

##### 877049: Betriebszustände des Prüflings während des Tests (definiert in Kapitel Betriebszustände): »...« (Customer Requirement)
- Acceptance: in evaluation
- Customer ID: STLH-3882
- Artifact Format: Text

##### 877050: Entladenetzwerk (ESDD-Test): 330 pF / 330 Ω (Customer Requirement)
- Acceptance: in evaluation
- Artifact Format: Text
- Customer ID: STLH-3885

##### 877051: Weitere Details u.a. zu den Entladepunkten sind in [MBN 10284-2] im Kapitel 19 zu finden. (Customer Requirement)
- Artifact Format: Text
- Customer ID: STLH-3886
- Acceptance: in evaluation

#### 877052: Elektrostatische Entladung (Powered Up) – Indirekte Entladung (ESDI-Test) (Heading Customer)
- Artifact Format: Text
- Customer ID: STLH-3887

##### 877053: Betriebszustände des Prüflings während des Tests (definiert in Kapitel Betriebszustände): »...« (Customer Requirement)
- Acceptance: in evaluation
- Customer ID: STLH-3888
- Artifact Format: Text

##### 877054: Entladenetzwerk (ESDI-Test): 330 pF / 330 Ω (Customer Requirement)
- Acceptance: in evaluation
- Customer ID: STLH-3891
- Artifact Format: Text

##### 877055: Weitere Details u.a. zu den Entladepunkten sind in [MBN 10284-2] im Kapitel 20 zu finden. (Customer Requirement)
- Acceptance: in evaluation
- Artifact Format: Text
- Customer ID: STLH-3892

### 877056: EMV-Anforderungen – Fahrzeugprüfungen (Heading Customer)
- Artifact Format: Text
- Customer ID: STLH-3893

#### 877057: Die Fahrzeugprüfungen werden beim Auftraggeber durchgeführt. (Information)
- Artifact Format: Text
- Customer ID: STLH-4704

#### 877058: Emissionsmessung an Fahrzeugantennen (CISPR25-Test) (Heading Customer)
- Customer ID: STLH-3894
- Artifact Format: Text

##### 877059: Betriebszustände des Prüflings während des Tests (definiert in Kapitel Betriebszustände): »...« (Customer Requirement)
- Acceptance: in evaluation
- Artifact Format: Text
- Customer ID: STLH-3895

##### 877060: Weitere Details sind in [MBN 10284-1] im Kapitel 5 zu finden. (Customer Requirement)
- Artifact Format: Text
- Customer ID: STLH-3897
- Acceptance: in evaluation

#### 877061: Emissionsmessung mit externer Antenne (CISPR12-Test) (Heading Customer)
- Artifact Format: Text
- Customer ID: STLH-3898

##### 877062 (Customer Requirement)
Die Betriebszustände des Fahrzeugs während des Tests sind in CISPR12 definiert:
- mit eingeschalteter Batterie, aber ausgeschaltetem Motor
- mit eingeschaltetem Motor (laufendem) Motor
- Acceptance: in evaluation
- Customer ID: STLH-3899
- Artifact Format: Text

##### 877063: Weitere Details sind in [MBN 10284-1] im Kapitel 6 zu finden. (Customer Requirement)
- Customer ID: STLH-3901
- Artifact Format: Text
- Acceptance: in evaluation

#### 877064: Magnetfeldemission (MFE-Test) (Heading Customer)
- Customer ID: STLH-3902
- Artifact Format: Text

##### 877065 (Customer Requirement)
Der Betriebszustand des Fahrzeugs während des Tests ist in CISPR12 definiert:
- mit eingeschaltetem Motor (laufendem) Motor
- Customer ID: STLH-3903
- Acceptance: in evaluation
- Artifact Format: Text

##### 877066: Weitere Details sind in [MBN 10284-1] im Kapitel 7 zu finden. (Customer Requirement)
- Acceptance: in evaluation
- Customer ID: STLH-3905
- Artifact Format: Text

#### 877067: Störfestigkeit; OPTION 1 – gegen externe Sender (OVRS-Test); OPTION 2 – in der Modenverwirbelungskammer (RC-Test) (Heading Customer)
- Artifact Format: Text
- Customer ID: STLH-3906

##### 877068: Betriebszustände des Fahrzeugs / des Prüflings während des Tests (definiert in Kapitel Betriebszustände): »...« (Customer Requirement)
- Customer ID: STLH-3907
- Acceptance: in evaluation
- Artifact Format: Text

##### 877069: Weitere Details sind in [MBN 10284-1] im Kapitel 8 (OVRS-Test) bzw. Kapitel 9 (RC-Test) zu finden. (Customer Requirement)
- Customer ID: STLH-3909
- Artifact Format: Text
- Acceptance: in evaluation

#### 877070: Störfestigkeit gegen im Fahrzeug vom Kunden installierte Sender (OBT-Test) (Heading Customer)
- Customer ID: STLH-3910
- Artifact Format: Text

##### 877071: Betriebszustände des Prüflings während des Tests (definiert in Kapitel Betriebszustände): »...« (Customer Requirement)
- Acceptance: in evaluation
- Artifact Format: Text
- Customer ID: STLH-3911

##### 877072: Weitere Details sind in [MBN 10284-1] im Kapitel 10 zu finden. (Customer Requirement)
- Acceptance: in evaluation
- Artifact Format: Text
- Customer ID: STLH-3913

#### 877073: Störfestigkeit gegen im Fahrzeug festinstallierte Sender (OBT2-Test) (Heading Customer)
- Customer ID: STLH-6243
- Artifact Format: Text

##### 877074: Betriebszustände des Fahrzeugs / des Prüflings während des Tests (definiert in Kapitel Betriebszustände): »...« (Customer Requirement)
- Customer ID: STLH-6244
- Acceptance: in evaluation
- Artifact Format: Text

##### 877075: Weitere Details sind in [MBN 10284-1] im Kapitel 11 zu finden. (Customer Requirement)
- Artifact Format: Text
- Acceptance: in evaluation
- Customer ID: STLH-6245

#### 877076: Störfestigkeit gegen tragbare Sender (PT-Test) (Heading Customer)
- Artifact Format: Text
- Customer ID: STLH-3914

##### 877077: Betriebszustände des Prüflings während des Tests (definiert in Kapitel Betriebszustände): »...« (Customer Requirement)
- Customer ID: STLH-3915
- Acceptance: in evaluation
- Artifact Format: Text

##### 877078: Weitere Details sind in [MBN 10284-1] im Kapitel 12 zu finden. (Customer Requirement)
- Artifact Format: Text
- Acceptance: in evaluation
- Customer ID: STLH-3917

#### 877079: Elektrostatische Entladungen (ESD-Test) (Heading Customer)
- Artifact Format: Text
- Customer ID: STLH-3918

##### 877080: Betriebszustände des Prüflings während des Tests (definiert in Kapitel Betriebszustände): »...« (Customer Requirement)
- Customer ID: STLH-3919
- Artifact Format: Text
- Acceptance: in evaluation

##### 877081: Entladenetzwerk (ESD-Test): »...« (150 pF / 330 Ω bzw. 330 pF / 330 Ω) (Customer Requirement)
- Customer ID: STLH-3923
- Acceptance: in evaluation
- Artifact Format: Text

##### 877082: Anmerkung: Eine indirekte Entladung an metallische Strukturen im Ein-/Ausstiegsbereich (z. B. A-Säulen, Tür) wird generell durchgeführt (Entladenetzwerk 330 pF / 330 Ω). (Information)
- Customer ID: STLH-3924
- Artifact Format: Text

##### 877083: Weitere Details u.a. zu den Entladepunkten sind in [MBN 10284-1] im Kapitel 13 zu finden. (Customer Requirement)
- Artifact Format: Text
- Customer ID: STLH-3925
- Acceptance: in evaluation
