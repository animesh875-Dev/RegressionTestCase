# IBM Engineering Requirements Wed May 10 12:24:20 CEST 2023

# Specification: TestNewArtifact_EditName_AfterBaseline
- Artifact Format: Module
- ReqIF.Name: TestNewArtifact_EditName_AfterBaseline

## 2454083: qwe (Heading)
- Artifact Format: Text
- Heading: 10
- ChapterName: Artifact content for testing TS 14494
- Deviation Exist: No
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
## 2454085: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 (Heading)
- Artifact Format: Text
- Heading: 10
- Deviation Exist: No

## 2454086: Cat reqif A3 (Heading)
- ChapterName: Cat reqif A3
  | Header | Value |
  | --- | --- |
- Deviation Exist: No
- Artifact Format: Text
- Heading: 10

## 2454087: Cat reqif A4 Symbols ✓ψ≅→™∝∑® (Heading)
- Deviation Exist: No
- Heading: 10
- Name: Cat reqif A4 Symbols
- Artifact Format: Text

## 2454093: 10 (Information)
Cat reqif A5 Artifact
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- Platform Category: Core
- Name: Cat reqif A5 Artifact
- Deviation Exist: No
- Artifact Format: Text

## 2454084: img-01111616.png (Heading)
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- Deviation Exist: No
- Artifact Format: File
- Heading: 10

## 2454090: 10 (Heading)
cat r2 reqif2
- Deviation Exist: No
- Artifact Format: Text
